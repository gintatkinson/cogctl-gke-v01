module ietf-otn-topology {
     yang-version 1.1;
     namespace "urn:ietf:params:xml:ns:yang:ietf-otn-topology";
     prefix "otnt";

     import ietf-network {
       prefix "nw";
       reference "RFC 8345: A YANG Data Model for Network Topologies";
     }

     import ietf-network-topology {
       prefix "nt";
       reference "RFC 8345: A YANG Data Model for Network Topologies";
     }

     import ietf-te-topology {
       prefix "tet";
       reference
         "RFC 8795: YANG Data Model for Traffic Engineering
          (TE) Topologies";
     }

     import ietf-layer1-types {
       prefix "l1-types";
       reference
         "I-D.ietf-ccamp-layer1-types: A YANG Data Model
          for Layer 1 Types";
     }

     organization
       "IETF CCAMP Working Group";
     contact
       "WG Web: <https://datatracker.ietf.org/wg/ccamp/>
        WG List: <mailto:ccamp@ietf.org>

        Editor: Haomian Zheng
                <mailto:zhenghaomian@huawei.com>

        Editor: Italo Busi
                <mailto:italo.busi@huawei.com>

        Editor: Xufeng Liu
                <mailto:xufeng.liu.ietf@gmail.com>

        Editor: Sergio Belotti
                <mailto:sergio.belotti@nokia.com>




        Editor: Oscar Gonzalez de Dios
                <mailto:oscar.gonzalezdedios@telefonica.com>";

     description
       "This module defines a protocol independent Layer 1/ODU topology
        data model. The model fully conforms
        to the Network Management Datastore Architecture (NMDA).

        Copyright (c) 2023 IETF Trust and the persons identified
        as authors of the code.  All rights reserved.

        Redistribution and use in source and binary forms, with or
        without modification, is permitted pursuant to, and subject
        to the license terms contained in, the Revised BSD License
        set forth in Section 4.c of the IETF Trust's Legal Provisions
        Relating to IETF Documents
        (https://trustee.ietf.org/license-info).

        This version of this YANG module is part of RFC XXXX; see
        the RFC itself for full legal notices.

        The key words 'MUST', 'MUST NOT', 'REQUIRED', 'SHALL', 'SHALL
        NOT', 'SHOULD', 'SHOULD NOT', 'RECOMMENDED', 'NOT RECOMMENDED',
        'MAY', and 'OPTIONAL' in this document are to be interpreted as
        described in BCP 14 (RFC 2119) (RFC 8174) when, and only when,
        they appear in all capitals, as shown here.";

     revision 2023-07-06 {
       description
         "Initial Revision";
       reference
         "RFC XXXX: A YANG Data Model for Optical Transport Network
         Topology";
       // RFC Ed.: replace XXXX with actual RFC number, update date
       // information and remove this note
     }

     /*
      * Groupings
      */

     grouping label-range-info {
       description
         "OTN technology-specific label range related information with
         a presence container indicating that the label range is an
         OTN technology-specific label range.

         This grouping SHOULD be used together with the




         otn-label-start-end and otn-label-step groupings to provide
         OTN technology-specific label information to the models which
         use the label-restriction-info grouping defined in the module
         ietf-te-types.";
       uses l1-types:otn-label-range-info {
         refine otn-label-range {
           presence
             "Indicates the label range is an OTN label range.

             This container MUST NOT be present if there are other
             presence containers or attributes indicating another type
             of label range.";
         }
       }
     }

    /*
     * Data nodes
     */

     augment "/nw:networks/nw:network/nw:network-types/"
           + "tet:te-topology" {
       container otn-topology {
         presence "indicates a topology type of Optical Transport
                   Network (OTN)-electrical layer.";
         description "OTN topology type";
       }
       description "augment network types to include OTN newtork";
     }

     augment "/nw:networks/nw:network/nw:node/tet:te"
           + "/tet:te-node-attributes" {
       when "../../../nw:network-types/tet:te-topology/"
          + "otnt:otn-topology" {
         description "Augment only for OTN network.";
       }
       description "Augment TE node attributes.";
       container otn-node {
         presence "The TE node is an OTN node.";
         description
           "Introduce new TE node type for OTN node.";
       }
     }

     augment "/nw:networks/nw:network/nt:link/tet:te/"
           + "tet:te-link-attributes" {
       when "../../../nw:network-types/tet:te-topology/"
          + "otnt:otn-topology" {




         description "Augment only for OTN network.";
       }
       description "Augment link configuration";

       container otn-link {
         description
           "Attributes of the OTN Link.";
         leaf odtu-flex-type {
           type l1-types:odtu-flex-type;
           description
             "The type of Optical Data Tributary Unit (ODTU)
             whose nominal bitrate is used to compute the number of
             Tributary Slots (TS) required by the ODUflex LSPs set up
             on this OTN Link.";
         }
         leaf tsg {
           type identityref {
             base l1-types:tributary-slot-granularity;
           }
           description "Tributary slot granularity.";
           reference
             "ITU-T G.709 v6.0 (06/2020): Interfaces for the Optical
             Transport Network (OTN)";
         }
         leaf distance {
           type uint32;
           description "distance in the unit of kilometers";
         }
       }
       container client-svc {
         presence
           "When present, indicates that the Link supports Costant
           Bit Rate (CBR) client signals.";
         description
           "Attributes of the Link supporting CBR client signals.";
         leaf-list supported-client-signal {
           type identityref {
             base l1-types:client-signal;
           }
           min-elements 1;
           description
             "List of client signal types supported by the Link.";
         }
       }
     }

     augment "/nw:networks/nw:network/nw:node/nt:termination-point/"
           + "tet:te" {




       when "../../../nw:network-types/tet:te-topology/"
          + "otnt:otn-topology" {
         description "Augment only for OTN network";
       }
       description "OTN TP attributes config in ODU topology.";

       container otn-ltp {
         description
           "Attributes of the OTN Link Termination Point (LTP).";
         leaf odtu-flex-type {
           type l1-types:odtu-flex-type;
           description
             "The type of Optical Data Tributary Unit (ODTU)
             whose nominal bitrate is used to compute the number of
             Tributary Slots (TS) required by the ODUflex LSPs set up
             on this OTN Link Termination Point (LTP).";
         }
       }
       container client-svc {
         presence
           "When present, indicates that the Link Termination Point
           (LTP) supports Costant Bit Rate (CBR) client signals.";
         description
           "OTN LTP Service attributes.";
         leaf-list supported-client-signal {
           type identityref {
             base l1-types:client-signal;
           }
           description
             "List of client signal types supported by the LTP.";
         }
       }
     }

     /*
      * Augment TE bandwidth
      */

     augment "/nw:networks/nw:network/nw:node/nt:termination-point/"
           + "tet:te/"
           + "tet:interface-switching-capability/tet:max-lsp-bandwidth/"
           + "tet:te-bandwidth/tet:technology" {
       when "../../../../../../nw:network-types/tet:te-topology/"
          + "otnt:otn-topology" {
         description
           "Augmentation parameters apply only for networks with
            OTN topology type.";
       }




       description
         "Augment maximum LSP TE bandwidth for the link termination
          point (LTP).";
       case otn {
         uses l1-types:otn-max-path-bandwidth {
           description
             "The odtu-flex-type attribute of the OTN Link Termination
             Point (LTP) is used to compute the number of Tributary
             Slots (TS) required by the ODUflex LSPs set up on this
             OTN LTP.";
         }
       }
     }

     augment "/nw:networks/nw:network/nw:node/tet:te/"
           + "tet:te-node-attributes/tet:connectivity-matrices/"
           + "tet:path-constraints/tet:te-bandwidth/tet:technology" {
       when "../../../../../../nw:network-types/tet:te-topology/"
          + "otnt:otn-topology" {
         description
           "Augmentation parameters apply only for networks with
            OTN topology type.";
       }
       description
         "Augment TE bandwidth path constraints of the TE node
          connectivity matrices.";
       case otn {
         uses l1-types:otn-link-bandwidth {
           augment otn {
             description
               "Augment OTN link bandwidth information.";
             leaf odtu-flex-type {
               type l1-types:odtu-flex-type;
               description
                 "The type of Optical Data Tributary Unit (ODTU)
                 whose nominal bitrate is used to compute the number of
                 Tributary Slots (TS) required by the ODUflex LSPs
                 set up along the underlay paths of these OTN
                 connectivity matrices.";
             }
           }
         }
       }
     }

     augment "/nw:networks/nw:network/nw:node/tet:te/"
           + "tet:te-node-attributes/tet:connectivity-matrices/"
           + "tet:connectivity-matrix/"




           + "tet:path-constraints/tet:te-bandwidth/tet:technology" {
       when "../../../../../../../nw:network-types/tet:te-topology/"
          + "otnt:otn-topology" {
         description
           "Augmentation parameters apply only for networks with
            OTN topology type.";
       }
       description
         "Augment TE bandwidth path constraints of the
          connectivity matrix entry.";
       case otn {
         uses l1-types:otn-link-bandwidth {
           augment otn {
             description
               "Augment OTN link bandwidth information.";
             leaf odtu-flex-type {
               type l1-types:odtu-flex-type;
               description
                 "The type of Optical Data Tributary Unit (ODTU)
                 whose nominal bitrate is used to compute the number of
                 Tributary Slots (TS) required by the ODUflex LSPs
                 set up along the underlay path of this OTN
                 connectivity matrix entry.";
             }
           }
         }
       }
     }

     augment "/nw:networks/nw:network/nw:node/tet:te/"
           + "tet:information-source-entry/tet:connectivity-matrices/"
           + "tet:path-constraints/tet:te-bandwidth/tet:technology" {
       when "../../../../../../nw:network-types/tet:te-topology/"
          + "otnt:otn-topology" {
         description
           "Augmentation parameters apply only for networks with
            OTN topology type.";
       }
       description
         "Augment TE bandwidth path constraints of the TE node
          connectivity matrices information source.";
       case otn {
         uses l1-types:otn-link-bandwidth {
           augment otn {
             description
               "Augment OTN link bandwidth information.";
             leaf odtu-flex-type {
               type l1-types:odtu-flex-type;




               description
                 "The type of Optical Data Tributary Unit (ODTU)
                 whose nominal bitrate is used to compute the number of
                 Tributary Slots (TS) required by the ODUflex LSPs
                 set up along the underlay paths of these OTN
                 connectivity matrices.";
             }
           }
         }
       }
     }

     augment "/nw:networks/nw:network/nw:node/tet:te/"
           + "tet:information-source-entry/tet:connectivity-matrices/"
           + "tet:connectivity-matrix/"
           + "tet:path-constraints/tet:te-bandwidth/tet:technology" {
       when "../../../../../../../nw:network-types/tet:te-topology/"
          + "otnt:otn-topology" {
         description
           "Augmentation parameters apply only for networks with
            OTN topology type.";
       }
       description
         "Augment TE bandwidth path constraints of the
          connectivity matrix entry information source";
       case otn {
         uses l1-types:otn-link-bandwidth {
           augment otn {
             description
               "Augment OTN link bandwidth information.";
             leaf odtu-flex-type {
               type l1-types:odtu-flex-type;
               description
                 "The type of Optical Data Tributary Unit (ODTU)
                 whose nominal bitrate is used to compute the number of
                 Tributary Slots (TS) required by the ODUflex LSPs
                 set up along the underlay path of this OTN
                 connectivity matrix entry.";
             }
           }
         }
       }
     }

     augment "/nw:networks/nw:network/nw:node/tet:te/"
           + "tet:tunnel-termination-point/"
           + "tet:client-layer-adaptation/tet:switching-capability/"
           + "tet:te-bandwidth/tet:technology" {




       when "../../../../../../nw:network-types/tet:te-topology/"
          + "otnt:otn-topology" {
         description
           "Augmentation parameters apply only for networks with
            OTN topology type.";
       }
       description
         "Augment client TE bandwidth of the tunnel termination point
          (TTP)";
       case otn {
         uses l1-types:otn-link-bandwidth {
           augment otn {
             description
               "Augment OTN link bandwidth information.";
             leaf odtu-flex-type {
               type l1-types:odtu-flex-type;
               description
                 "The type of Optical Data Tributary Unit (ODTU)
                 whose nominal bitrate is used to compute the number of
                 Tributary Slots (TS) required by the ODUflex LSPs
                 terminated on this OTN Tunnel Termination Point
                 (TTP).";
             }
           }
         }
       }
     }

     augment "/nw:networks/nw:network/nw:node/tet:te/"
           + "tet:tunnel-termination-point/"
           + "tet:local-link-connectivities/tet:path-constraints/"
           + "tet:te-bandwidth/tet:technology" {
       when "../../../../../../nw:network-types/tet:te-topology/"
          + "otnt:otn-topology" {
         description
           "Augmentation parameters apply only for networks with
            OTN topology type.";
       }
       description
         "Augment TE bandwidth path constraints for the TTP
          Local Link Connectivities.";
       case otn {
         uses l1-types:otn-link-bandwidth {
           augment otn {
             description
               "Augment OTN link bandwidth information.";
             leaf odtu-flex-type {
               type l1-types:odtu-flex-type;




               description
                 "The type of Optical Data Tributary Unit (ODTU)
                 whose nominal bitrate is used to compute the number of
                 Tributary Slots (TS) required by the ODUflex LSPs
                 set up along the underlay paths of these OTN Local
                 Link Connectivities.";
             }
           }
         }
       }
     }

     augment "/nw:networks/nw:network/nw:node/tet:te/"
           + "tet:tunnel-termination-point/"
           + "tet:local-link-connectivities/"
           + "tet:local-link-connectivity/tet:path-constraints/"
           + "tet:te-bandwidth/tet:technology" {
       when "../../../../../../../nw:network-types/tet:te-topology/"
          + "otnt:otn-topology" {
         description
           "Augmentation parameters apply only for networks with
            OTN topology type.";
       }
       description
         "Augment TE bandwidth path constraints for the TTP
          Local Link Connectivity entry.";
       case otn {
         uses l1-types:otn-link-bandwidth {
           augment otn {
             description
               "Augment OTN link bandwidth information.";
             leaf odtu-flex-type {
               type l1-types:odtu-flex-type;
               description
                 "The type of Optical Data Tributary Unit (ODTU)
                 whose nominal bitrate is used to compute the number of
                 Tributary Slots (TS) required by the ODUflex LSPs
                 set up along the underlay path of this OTN Local
                 Link Connectivyt entry.";
             }
           }
         }
       }
     }

     augment "/nw:networks/nw:network/nt:link/tet:te/"
           + "tet:te-link-attributes/"
           + "tet:interface-switching-capability/tet:max-lsp-bandwidth/"




           + "tet:te-bandwidth/tet:technology" {
       when "../../../../../../nw:network-types/tet:te-topology/"
          + "otnt:otn-topology" {
         description
           "Augmentation parameters apply only for networks with
            OTN topology type.";
       }
       description
         "Augment maximum LSP TE bandwidth for the TE link.";
       case otn {
         uses l1-types:otn-max-path-bandwidth {
           description
             "The odtu-flex-type attribute of the OTN Link is used
             to compute the number of Tributary Slots (TS) required
             by the ODUflex LSPs set up on this OTN Link.";
         }
       }
     }

     augment "/nw:networks/nw:network/nt:link/tet:te/"
           + "tet:te-link-attributes/"
           + "tet:max-link-bandwidth/"
           + "tet:te-bandwidth" {
       when "../../../../../nw:network-types/tet:te-topology/"
          + "otnt:otn-topology" {
         description
           "Augmentation parameters apply only for networks with
            OTN topology type.";
       }
       description
         "Augment maximum TE bandwidth for the TE link";
       uses l1-types:otn-link-bandwidth {
         description
           "The odtu-flex-type attribute of the OTN Link is used
           to compute the number of Tributary Slots (TS) required
           by the ODUflex LSPs set up on this OTN Link.";
       }
     }

     augment "/nw:networks/nw:network/nt:link/tet:te/"
           + "tet:te-link-attributes/"
           + "tet:max-resv-link-bandwidth/"
           + "tet:te-bandwidth" {
       when "../../../../../nw:network-types/tet:te-topology/"
          + "otnt:otn-topology" {
         description
           "Augmentation parameters apply only for networks with
            OTN topology type.";




       }
       description
         "Augment maximum reservable TE bandwidth for the TE link";
       uses l1-types:otn-link-bandwidth {
         description
           "The odtu-flex-type attribute of the OTN Link is used
           to compute the number of Tributary Slots (TS) required
           by the ODUflex LSPs set up on this OTN Link.";
       }
     }

     augment "/nw:networks/nw:network/nt:link/tet:te/"
           + "tet:te-link-attributes/"
           + "tet:unreserved-bandwidth/"
           + "tet:te-bandwidth" {
       when "../../../../../nw:network-types/tet:te-topology/"
          + "otnt:otn-topology" {
         description
           "Augmentation parameters apply only for networks with
            OTN topology type.";
       }
       description
         "Augment unreserved TE bandwidth for the TE Link";
       uses l1-types:otn-link-bandwidth {
         description
           "The odtu-flex-type attribute of the OTN Link is used
           to compute the number of Tributary Slots (TS) required
           by the ODUflex LSPs set up on this OTN Link.";
       }
     }

     augment "/nw:networks/nw:network/nt:link/tet:te/"
           + "tet:information-source-entry/"
           + "tet:interface-switching-capability/"
           + "tet:max-lsp-bandwidth/"
           + "tet:te-bandwidth/tet:technology" {
       when "../../../../../../nw:network-types/tet:te-topology/"
          + "otnt:otn-topology" {
         description
           "Augmentation parameters apply only for networks with
            OTN topology type.";
       }
       description
         "Augment maximum LSP TE bandwidth for the TE link
          information source";
       case otn {
         uses l1-types:otn-max-path-bandwidth {
           description




             "The odtu-flex-type attribute of the OTN Link is used
             to compute the number of Tributary Slots (TS) required
             by the ODUflex LSPs set up on this OTN Link.";
         }
       }
     }

     augment "/nw:networks/nw:network/nt:link/tet:te/"
           + "tet:information-source-entry/"
           + "tet:max-link-bandwidth/"
           + "tet:te-bandwidth" {
       when "../../../../../nw:network-types/tet:te-topology/"
          + "otnt:otn-topology" {
         description
           "Augmentation parameters apply only for networks with
            OTN topology type.";
       }
       description
         "Augment maximum TE bandwidth for the TE link
          information source";
       uses l1-types:otn-link-bandwidth {
         description
           "The odtu-flex-type attribute of the OTN Link is used
           to compute the number of Tributary Slots (TS) required
           by the ODUflex LSPs set up on this OTN Link.";
       }
     }

     augment "/nw:networks/nw:network/nt:link/tet:te/"
           + "tet:information-source-entry/"
           + "tet:max-resv-link-bandwidth/"
           + "tet:te-bandwidth" {
       when "../../../../../nw:network-types/tet:te-topology/"
          + "otnt:otn-topology" {
         description
           "Augmentation parameters apply only for networks with
            OTN topology type.";
       }
       description
         "Augment maximum reservable TE bandwidth for the TE link
          information-source";
       uses l1-types:otn-link-bandwidth {
         description
           "The odtu-flex-type attribute of the OTN Link is used
           to compute the number of Tributary Slots (TS) required
           by the ODUflex LSPs set up on this OTN Link.";
       }
     }




     augment "/nw:networks/nw:network/nt:link/tet:te/"
           + "tet:information-source-entry/"
           + "tet:unreserved-bandwidth/"
           + "tet:te-bandwidth" {
       when "../../../../../nw:network-types/tet:te-topology/"
          + "otnt:otn-topology" {
         description
           "Augmentation parameters apply only for networks with
            OTN topology type.";
       }
       description
         "Augment unreserved TE bandwidth of the TE link
          information source";
       uses l1-types:otn-link-bandwidth {
         description
           "The odtu-flex-type attribute of the OTN Link is used
           to compute the number of Tributary Slots (TS) required
           by the ODUflex LSPs set up on this OTN Link.";
       }
     }

     augment "/nw:networks/tet:te/tet:templates/"
           + "tet:link-template/tet:te-link-attributes/"
           + "tet:interface-switching-capability/"
           + "tet:max-lsp-bandwidth/"
           + "tet:te-bandwidth/tet:technology" {
       description
         "Augment maximum LSP TE bandwidth of the TE link
          template";
       case otn {
         uses l1-types:otn-max-path-bandwidth {
           description
             "The odtu-flex-type attribute of the OTN Link is used
             to compute the number of Tributary Slots (TS) required
             by the ODUflex LSPs set up on the OTN Link that uses this
             Link Template.";
         }
       }
     }

     augment "/nw:networks/tet:te/tet:templates/"
           + "tet:link-template/tet:te-link-attributes/"
           + "tet:max-link-bandwidth/"
           + "tet:te-bandwidth" {
       description
         "Augment maximum TE bandwidth the TE link template";
       uses l1-types:otn-link-bandwidth {
         description




           "The odtu-flex-type attribute of the OTN Link is used
           to compute the number of Tributary Slots (TS) required
           by the ODUflex LSPs set up on the OTN Link that uses this
           Link Template.";
       }
     }

     augment "/nw:networks/tet:te/tet:templates/"
           + "tet:link-template/tet:te-link-attributes/"
           + "tet:max-resv-link-bandwidth/"
           + "tet:te-bandwidth" {
       description
         "Augment maximum reservable TE bandwidth for the TE link
          template.";
       uses l1-types:otn-link-bandwidth {
         description
           "The odtu-flex-type attribute of the OTN Link is used
           to compute the number of Tributary Slots (TS) required
           by the ODUflex LSPs set up on the OTN Link that uses this
           Link Template.";
       }
     }

     augment "/nw:networks/tet:te/tet:templates/"
           + "tet:link-template/tet:te-link-attributes/"
           + "tet:unreserved-bandwidth/"
           + "tet:te-bandwidth" {
       description
         "Augment unreserved TE bandwidth the TE link template";
       uses l1-types:otn-link-bandwidth {
         description
           "The odtu-flex-type attribute of the OTN Link is used
           to compute the number of Tributary Slots (TS) required
           by the ODUflex LSPs set up on the OTN Link that uses this
           Link Template.";
       }
     }

     /*
      * Augment TE label range information
      */

     augment "/nw:networks/nw:network/nw:node/tet:te/"
           + "tet:te-node-attributes/tet:connectivity-matrices/"
           + "tet:label-restrictions/tet:label-restriction" {
       when "../../../../../../nw:network-types/tet:te-topology/"
          + "otnt:otn-topology" {
         description




           "Augmentation parameters apply only for networks with
            OTN topology type.";
       }
       description
         "Augment TE label range information for the TE node
          connectivity matrices.";
       uses label-range-info;
     }

     augment "/nw:networks/nw:network/nw:node/tet:te/"
           + "tet:te-node-attributes/tet:connectivity-matrices/"
           + "tet:connectivity-matrix/tet:from/"
           + "tet:label-restrictions/tet:label-restriction" {
       when "../../../../../../../../nw:network-types/tet:te-topology/"
          + "otnt:otn-topology" {
         description
           "Augmentation parameters apply only for networks with
            OTN topology type.";
       }
       description
         "Augment TE label range information for the source LTP
          of the connectivity matrix entry.";
       uses label-range-info;
     }

     augment "/nw:networks/nw:network/nw:node/tet:te/"
           + "tet:te-node-attributes/tet:connectivity-matrices/"
           + "tet:connectivity-matrix/tet:to/"
           + "tet:label-restrictions/tet:label-restriction" {
       when "../../../../../../../../nw:network-types/tet:te-topology/"
          + "otnt:otn-topology" {
         description
           "Augmentation parameters apply only for networks with
            OTN topology type.";
       }
       description
         "Augment TE label range information for the destination LTP
          of the connectivity matrix entry.";
       uses label-range-info;
     }

     augment "/nw:networks/nw:network/nw:node/tet:te/"
           + "tet:information-source-entry/"
           + "tet:connectivity-matrices/tet:label-restrictions/"
           + "tet:label-restriction" {
       when "../../../../../../nw:network-types/tet:te-topology/"
          + "otnt:otn-topology" {
         description




           "Augmentation parameters apply only for networks with
            OTN topology type.";
       }
       description
         "Augment TE label range information for the TE node
          connectivity matrices information source.";
       uses label-range-info;
     }

     augment "/nw:networks/nw:network/nw:node/tet:te/"
           + "tet:information-source-entry/tet:connectivity-matrices/"
           + "tet:connectivity-matrix/"
           + "tet:from/tet:label-restrictions/tet:label-restriction" {
       when "../../../../../../../../nw:network-types/tet:te-topology/"
          + "otnt:otn-topology" {
         description
           "Augmentation parameters apply only for networks with
            OTN topology type.";
       }
       description
         "Augment TE label range information for the source LTP
          of the connectivity matrix entry information source.";
       uses label-range-info;
     }

     augment "/nw:networks/nw:network/nw:node/tet:te/"
           + "tet:information-source-entry/tet:connectivity-matrices/"
           + "tet:connectivity-matrix/"
           + "tet:to/tet:label-restrictions/tet:label-restriction" {
       when "../../../../../../../../nw:network-types/tet:te-topology/"
          + "otnt:otn-topology" {
         description
           "Augmentation parameters apply only for networks with
            OTN topology type.";
       }
       description
         "Augment TE label range information for the destination LTP
          of the connectivity matrix entry information source.";
       uses label-range-info;
     }

     augment "/nw:networks/nw:network/nw:node/tet:te/"
           + "tet:tunnel-termination-point/"
           + "tet:local-link-connectivities/"
           + "tet:label-restrictions/tet:label-restriction" {
       when "../../../../../../nw:network-types/tet:te-topology/"
          + "otnt:otn-topology" {
         description




           "Augmentation parameters apply only for networks with
            OTN topology type.";
       }
       description
         "Augment TE label range information for the TTP
          Local Link Connectivities.";
       uses label-range-info;
     }

     augment "/nw:networks/nw:network/nw:node/tet:te/"
           + "tet:tunnel-termination-point/"
           + "tet:local-link-connectivities/"
           + "tet:local-link-connectivity/"
           + "tet:label-restrictions/tet:label-restriction" {
       when "../../../../../../../nw:network-types/tet:te-topology/"
          + "otnt:otn-topology" {
         description
           "Augmentation parameters apply only for networks with
            OTN topology type.";
       }
       description
         "Augment TE label range information for the TTP
          Local Link Connectivity entry.";
       uses label-range-info;
     }

     augment "/nw:networks/nw:network/nt:link/tet:te/"
           + "tet:te-link-attributes/"
           + "tet:label-restrictions/tet:label-restriction" {
       when "../../../../../nw:network-types/tet:te-topology/"
          + "otnt:otn-topology" {
         description
           "Augmentation parameters apply only for networks with
            OTN topology type.";
       }
       description
         "Augment TE label range information for the TE link.";
       uses label-range-info;
     }

     augment "/nw:networks/nw:network/nt:link/tet:te/"
           + "tet:information-source-entry/"
           + "tet:label-restrictions/tet:label-restriction" {
       when "../../../../../nw:network-types/tet:te-topology/"
          + "otnt:otn-topology" {
         description
           "Augmentation parameters apply only for networks with
            OTN topology type.";




       }
       description
         "Augment TE label range information for the TE link
          information source.";
       uses label-range-info;
     }

     augment "/nw:networks/tet:te/tet:templates/"
           + "tet:link-template/tet:te-link-attributes/"
           + "tet:label-restrictions/tet:label-restriction" {
       description
         "Augment TE label range information for the TE link template.";
       uses label-range-info;
     }

     /*
      * Augment TE label
      */

     augment "/nw:networks/nw:network/nw:node/tet:te/"
           + "tet:te-node-attributes/tet:connectivity-matrices/"
           + "tet:label-restrictions/tet:label-restriction/"
           + "tet:label-start/"
           + "tet:te-label/tet:technology" {
       when "../../../../../../../../nw:network-types/tet:te-topology/"
          + "otnt:otn-topology" {
         description
           "Augmentation parameters apply only for networks with
            OTN topology type.";
       }
       description
         "Augment TE label range start for the TE node
          connectivity matrices";
       case otn {
         uses l1-types:otn-label-start-end;
       }
     }

     augment "/nw:networks/nw:network/nw:node/tet:te/"
           + "tet:te-node-attributes/tet:connectivity-matrices/"
           + "tet:label-restrictions/"
           + "tet:label-restriction/tet:label-end/"
           + "tet:te-label/tet:technology" {
       when "../../../../../../../../nw:network-types/tet:te-topology/"
          + "otnt:otn-topology" {
         description
           "Augmentation parameters apply only for networks with
            OTN topology type.";




       }
       description
         "Augment TE label range end for the TE node
          connectivity matrices";
       case otn {
         uses l1-types:otn-label-start-end;
       }
     }

     augment "/nw:networks/nw:network/nw:node/tet:te/"
           + "tet:te-node-attributes/tet:connectivity-matrices/"
           + "tet:label-restrictions/"
           + "tet:label-restriction/tet:label-step/"
           + "tet:technology" {
       when "../../../../../../../nw:network-types/tet:te-topology/"
          + "otnt:otn-topology" {
         description
           "Augmentation parameters apply only for networks with
            OTN topology type.";
       }
       description
         "Augment TE label range step for the TE node
          connectivity matrices";
       case otn {
         uses l1-types:otn-label-step;
       }
     }

     augment "/nw:networks/nw:network/nw:node/tet:te/"
           + "tet:te-node-attributes/tet:connectivity-matrices/"
           + "tet:underlay/tet:primary-path/tet:path-element/"
           + "tet:type/tet:label/tet:label-hop/"
           + "tet:te-label/tet:technology" {
       when "../../../../../../../../../"
          + "nw:network-types/tet:te-topology/"
          + "otnt:otn-topology" {
         description
           "Augmentation parameters apply only for networks with
            OTN topology type.";
       }
       description
         "Augment TE label hop for the underlay primary path of the
          TE node connectivity matrices";
       case otn {
         uses l1-types:otn-label-hop;
       }
     }




     augment "/nw:networks/nw:network/nw:node/tet:te/"
           + "tet:te-node-attributes/tet:connectivity-matrices/"
           + "tet:underlay/tet:backup-path/tet:path-element/"
           + "tet:type/tet:label/tet:label-hop/"
           + "tet:te-label/tet:technology" {
       when "../../../../../../../../../"
          + "nw:network-types/tet:te-topology/"
          + "otnt:otn-topology" {
         description
           "Augmentation parameters apply only for networks with
            OTN topology type.";
       }
       description
         "Augment TE label hop for the underlay backup path of the
          TE node connectivity matrices";
       case otn {
         uses l1-types:otn-label-hop;
       }
     }

     augment "/nw:networks/nw:network/nw:node/tet:te/"
           + "tet:te-node-attributes/tet:connectivity-matrices/"
           + "tet:optimizations/tet:algorithm/tet:metric/"
           + "tet:optimization-metric/"
           + "tet:explicit-route-exclude-objects/"
           + "tet:route-object-exclude-object/"
           + "tet:type/tet:label/tet:label-hop/"
           + "tet:te-label/tet:technology" {
       when "../../../../../../../../../../"
          + "nw:network-types/tet:te-topology/"
          + "otnt:otn-topology" {
         description
           "Augmentation parameters apply only for networks with
            OTN topology type.";
       }
       description
         "Augment TE label hop for the explicit route objects excluded
          by the path computation of the TE node connectivity
          matrices";
       case otn {
         uses l1-types:otn-label-hop;
       }
     }

     augment "/nw:networks/nw:network/nw:node/tet:te/"
           + "tet:te-node-attributes/tet:connectivity-matrices/"
           + "tet:optimizations/tet:algorithm/tet:metric/"
           + "tet:optimization-metric/"




           + "tet:explicit-route-include-objects/"
           + "tet:route-object-include-object/"
           + "tet:type/tet:label/tet:label-hop/"
           + "tet:te-label/tet:technology" {
       when "../../../../../../../../../../"
          + "nw:network-types/tet:te-topology/"
          + "otnt:otn-topology" {
         description
           "Augmentation parameters apply only for networks with
            OTN topology type.";
       }
       description
         "Augment TE label hop for the explicit route objects included
          by the path computation of the TE node connectivity
          matrices";
       case otn {
         uses l1-types:otn-label-hop;
       }
     }

     augment "/nw:networks/nw:network/nw:node/tet:te/"
           + "tet:te-node-attributes/tet:connectivity-matrices/"
           + "tet:path-properties/tet:path-route-objects/"
           + "tet:path-route-object/tet:type/tet:label/tet:label-hop/"
           + "tet:te-label/tet:technology" {
       when "../../../../../../../../../"
          + "nw:network-types/tet:te-topology/"
          + "otnt:otn-topology" {
         description
           "Augmentation parameters apply only for networks with
            OTN topology type.";
       }
       description
         "Augment TE label hop for the computed path route objects
          of the TE node connectivity matrices";
       case otn {
         uses l1-types:otn-label-hop;
       }
     }

     augment "/nw:networks/nw:network/nw:node/tet:te/"
           + "tet:te-node-attributes/tet:connectivity-matrices/"
           + "tet:connectivity-matrix/tet:from/"
           + "tet:label-restrictions/tet:label-restriction/"
           + "tet:label-start/"
           + "tet:te-label/tet:technology" {
       when "../../../../../../../../../../"
          + "nw:network-types/tet:te-topology/"




          + "otnt:otn-topology" {
         description
           "Augmentation parameters apply only for networks with
            OTN topology type.";
       }
       description
         "Augment TE label range start for the source LTP
          of the connectivity matrix entry.";
       case otn {
         uses l1-types:otn-label-start-end;
       }
     }

     augment "/nw:networks/nw:network/nw:node/tet:te/"
           + "tet:te-node-attributes/tet:connectivity-matrices/"
           + "tet:connectivity-matrix/tet:from/"
           + "tet:label-restrictions/tet:label-restriction/"
           + "tet:label-end/"
           + "tet:te-label/tet:technology" {
       when "../../../../../../../../../../"
          + "nw:network-types/tet:te-topology/"
          + "otnt:otn-topology" {
         description
           "Augmentation parameters apply only for networks with
            OTN topology type.";
       }
       description
         "Augment TE label range end for the source LTP
          of the connectivity matrix entry.";
       case otn {
         uses l1-types:otn-label-start-end;
       }
     }

     augment "/nw:networks/nw:network/nw:node/tet:te/"
           + "tet:te-node-attributes/tet:connectivity-matrices/"
           + "tet:connectivity-matrix/tet:from/"
           + "tet:label-restrictions/tet:label-restriction/"
           + "tet:label-step/"
           + "tet:technology" {
       when "../../../../../../../../../"
          + "nw:network-types/tet:te-topology/"
          + "otnt:otn-topology" {
         description
           "Augmentation parameters apply only for networks with
            OTN topology type.";
       }
       description




         "Augment TE label range step for the source LTP
          of the connectivity matrix entry.";
       case otn {
         uses l1-types:otn-label-step;
       }
     }

     augment "/nw:networks/nw:network/nw:node/tet:te/"
           + "tet:te-node-attributes/tet:connectivity-matrices/"
           + "tet:connectivity-matrix/tet:to/"
           + "tet:label-restrictions/tet:label-restriction/"
           + "tet:label-start/"
           + "tet:te-label/tet:technology" {
       when "../../../../../../../../../../"
          + "nw:network-types/tet:te-topology/"
          + "otnt:otn-topology" {
         description
           "Augmentation parameters apply only for networks with
            OTN topology type.";
       }
       description
         "Augment TE label range start for the destination LTP
          of the connectivity matrix entry.";
       case otn {
         uses l1-types:otn-label-start-end;
       }
     }

     augment "/nw:networks/nw:network/nw:node/tet:te/"
           + "tet:te-node-attributes/tet:connectivity-matrices/"
           + "tet:connectivity-matrix/tet:to/"
           + "tet:label-restrictions/tet:label-restriction/"
           + "tet:label-end/"
           + "tet:te-label/tet:technology" {
       when "../../../../../../../../../../"
          + "nw:network-types/tet:te-topology/"
          + "otnt:otn-topology" {
         description
           "Augmentation parameters apply only for networks with
            OTN topology type.";
       }
       description
         "Augment TE label range end for the destination LTP
          of the connectivity matrix entry.";
       case otn {
         uses l1-types:otn-label-start-end;
       }
     }




     augment "/nw:networks/nw:network/nw:node/tet:te/"
           + "tet:te-node-attributes/tet:connectivity-matrices/"
           + "tet:connectivity-matrix/tet:to/"
           + "tet:label-restrictions/tet:label-restriction/"
           + "tet:label-step/"
           + "tet:technology" {
       when "../../../../../../../../../"
          + "nw:network-types/tet:te-topology/"
          + "otnt:otn-topology" {
         description
           "Augmentation parameters apply only for networks with
            OTN topology type.";
       }
       description
         "Augment TE label range step for the destination LTP
          of the connectivity matrix entry.";
       case otn {
         uses l1-types:otn-label-step;
       }
     }

     augment "/nw:networks/nw:network/nw:node/tet:te/"
           + "tet:te-node-attributes/tet:connectivity-matrices/"
           + "tet:connectivity-matrix/"
           + "tet:underlay/tet:primary-path/tet:path-element/"
           + "tet:type/tet:label/tet:label-hop/"
           + "tet:te-label/tet:technology" {
       when "../../../../../../../../../../"
          + "nw:network-types/tet:te-topology/"
          + "otnt:otn-topology" {
         description
           "Augmentation parameters apply only for networks with
            OTN topology type.";
       }
       description
         "Augment TE label hop for the underlay primary path
          of the connectivity matrix entry.";
       case otn {
         uses l1-types:otn-label-hop;
       }
     }

     augment "/nw:networks/nw:network/nw:node/tet:te/"
           + "tet:te-node-attributes/tet:connectivity-matrices/"
           + "tet:connectivity-matrix/"
           + "tet:underlay/tet:backup-path/tet:path-element/"
           + "tet:type/tet:label/tet:label-hop/"
           + "tet:te-label/tet:technology" {




       when "../../../../../../../../../../"
          + "nw:network-types/tet:te-topology/"
          + "otnt:otn-topology" {
         description
           "Augmentation parameters apply only for networks with
            OTN topology type.";
       }
       description
         "Augment TE label hop for the underlay backup path
          of the connectivity matrix entry.";
       case otn {
         uses l1-types:otn-label-hop;
       }
     }

     augment "/nw:networks/nw:network/nw:node/tet:te/"
           + "tet:te-node-attributes/tet:connectivity-matrices/"
           + "tet:connectivity-matrix/tet:optimizations/"
           + "tet:algorithm/tet:metric/tet:optimization-metric/"
           + "tet:explicit-route-exclude-objects/"
           + "tet:route-object-exclude-object/tet:type/"
           + "tet:label/tet:label-hop/tet:te-label/tet:technology" {
       when "../../../../../../../../../../../"
          + "nw:network-types/tet:te-topology/"
          + "otnt:otn-topology" {
         description
           "Augmentation parameters apply only for networks with
            OTN topology type.";
       }
       description
         "Augment TE label hop for the explicit route objects excluded
          by the path computation of the connectivity matrix entry.";
       case otn {
         uses l1-types:otn-label-hop;
       }
     }

     augment "/nw:networks/nw:network/nw:node/tet:te/"
           + "tet:te-node-attributes/tet:connectivity-matrices/"
           + "tet:connectivity-matrix/tet:optimizations/"
           + "tet:algorithm/tet:metric/tet:optimization-metric/"
           + "tet:explicit-route-include-objects/"
           + "tet:route-object-include-object/tet:type/"
           + "tet:label/tet:label-hop/tet:te-label/tet:technology" {
       when "../../../../../../../../../../../"
          + "nw:network-types/tet:te-topology/"
          + "otnt:otn-topology" {
         description




           "Augmentation parameters apply only for networks with
            OTN topology type.";
       }
       description
         "Augment TE label hop for the explicit route objects included
          by the path computation of the connectivity matrix entry.";
       case otn {
         uses l1-types:otn-label-hop;
       }
     }

     augment "/nw:networks/nw:network/nw:node/tet:te/"
           + "tet:te-node-attributes/tet:connectivity-matrices/"
           + "tet:connectivity-matrix/"
           + "tet:path-properties/tet:path-route-objects/"
           + "tet:path-route-object/tet:type/"
           + "tet:label/tet:label-hop/tet:te-label/tet:technology" {
       when "../../../../../../../../../../"
          + "nw:network-types/tet:te-topology/"
          + "otnt:otn-topology" {
         description
           "Augmentation parameters apply only for networks with
            OTN topology type.";
       }
       description
         "Augment TE label hop for the computed path route objects
          of the connectivity matrix entry.";
       case otn {
         uses l1-types:otn-label-hop;
       }
     }

     augment "/nw:networks/nw:network/nw:node/tet:te/"
           + "tet:information-source-entry/"
           + "tet:connectivity-matrices/tet:label-restrictions/"
           + "tet:label-restriction/"
           + "tet:label-start/tet:te-label/tet:technology" {
       when "../../../../../../../../"
          + "nw:network-types/tet:te-topology/"
          + "otnt:otn-topology" {
         description
           "Augmentation parameters apply only for networks with
            OTN topology type.";
       }
       description
         "Augment TE label range start for the TE node connectivity
          matrices information source.";
       case otn {




         uses l1-types:otn-label-start-end;
       }
     }

     augment "/nw:networks/nw:network/nw:node/tet:te/"
           + "tet:information-source-entry/"
           + "tet:connectivity-matrices/tet:label-restrictions/"
           + "tet:label-restriction/"
           + "tet:label-end/tet:te-label/tet:technology" {
       when "../../../../../../../../"
          + "nw:network-types/tet:te-topology/"
          + "otnt:otn-topology" {
         description
           "Augmentation parameters apply only for networks with
            OTN topology type.";
       }
       description
         "Augment TE label range end for the TE node connectivity
          matrices information source.";
       case otn {
         uses l1-types:otn-label-start-end;
       }
     }

     augment "/nw:networks/nw:network/nw:node/tet:te/"
           + "tet:information-source-entry/"
           + "tet:connectivity-matrices/tet:label-restrictions/"
           + "tet:label-restriction/"
           + "tet:label-step/tet:technology" {
       when "../../../../../../../"
          + "nw:network-types/tet:te-topology/"
          + "otnt:otn-topology" {
         description
           "Augmentation parameters apply only for networks with
            OTN topology type.";
       }
       description
         "Augment TE label range step for the TE node connectivity
          matrices information source.";
       case otn {
         uses l1-types:otn-label-step;
       }
     }

     augment "/nw:networks/nw:network/nw:node/tet:te/"
           + "tet:information-source-entry/tet:connectivity-matrices/"
           + "tet:underlay/tet:primary-path/tet:path-element/tet:type/"
           + "tet:label/tet:label-hop/tet:te-label/tet:technology" {




       when "../../../../../../../../../"
          + "nw:network-types/tet:te-topology/"
          + "otnt:otn-topology" {
         description
           "Augmentation parameters apply only for networks with
            OTN topology type.";
       }
       description
         "Augment TE label hop for the underlay primary path
          of the TE node connectivity matrices of the information
          source entry.";
       case otn {
         uses l1-types:otn-label-hop;
       }
     }

     augment "/nw:networks/nw:network/nw:node/tet:te/"
           + "tet:information-source-entry/tet:connectivity-matrices/"
           + "tet:underlay/tet:backup-path/tet:path-element/tet:type/"
           + "tet:label/tet:label-hop/tet:te-label/tet:technology" {
       when "../../../../../../../../../"
          + "nw:network-types/tet:te-topology/"
          + "otnt:otn-topology" {
         description
           "Augmentation parameters apply only for networks with
            OTN topology type.";
       }
       description
         "Augment TE label hop for the underlay backup path
          of the TE node connectivity matrices of the information
          source entry.";
       case otn {
         uses l1-types:otn-label-hop;
       }
     }

     augment "/nw:networks/nw:network/nw:node/tet:te/"
           + "tet:information-source-entry/tet:connectivity-matrices/"
           + "tet:optimizations/tet:algorithm/tet:metric/"
           + "tet:optimization-metric/"
           + "tet:explicit-route-exclude-objects/"
           + "tet:route-object-exclude-object/tet:type/"
           + "tet:label/tet:label-hop/tet:te-label/tet:technology" {
       when "../../../../../../../../../../"
          + "nw:network-types/tet:te-topology/"
          + "otnt:otn-topology" {
         description
           "Augmentation parameters apply only for networks with




            OTN topology type.";
       }
       description
         "Augment TE label hop for the explicit route objects excluded
          by the path computation of the TE node connectivity matrices
          information source.";
       case otn {
         uses l1-types:otn-label-hop;
       }
     }

     augment "/nw:networks/nw:network/nw:node/tet:te/"
           + "tet:information-source-entry/tet:connectivity-matrices/"
           + "tet:optimizations/tet:algorithm/tet:metric/"
           + "tet:optimization-metric/"
           + "tet:explicit-route-include-objects/"
           + "tet:route-object-include-object/tet:type/"
           + "tet:label/tet:label-hop/tet:te-label/tet:technology" {
       when "../../../../../../../../../../"
          + "nw:network-types/tet:te-topology/"
          + "otnt:otn-topology" {
         description
           "Augmentation parameters apply only for networks with
            OTN topology type.";
       }
       description
         "Augment TE label hop for the explicit route objects included
          by the path computation of the TE node connectivity matrices
          information source.";
       case otn {
         uses l1-types:otn-label-hop;
       }
     }

     augment "/nw:networks/nw:network/nw:node/tet:te/"
           + "tet:information-source-entry/tet:connectivity-matrices/"
           + "tet:path-properties/tet:path-route-objects/"
           + "tet:path-route-object/tet:type/"
           + "tet:label/tet:label-hop/tet:te-label/tet:technology" {
       when "../../../../../../../../../"
          + "nw:network-types/tet:te-topology/"
          + "otnt:otn-topology" {
         description
           "Augmentation parameters apply only for networks with
            OTN topology type.";
       }
       description
         "Augment TE label hop for the computed path route objects




          of the TE node connectivity matrices information source.";
       case otn {
         uses l1-types:otn-label-hop;
       }
     }

     augment "/nw:networks/nw:network/nw:node/tet:te/"
           + "tet:information-source-entry/tet:connectivity-matrices/"
           + "tet:connectivity-matrix/"
           + "tet:from/tet:label-restrictions/"
           + "tet:label-restriction/"
           + "tet:label-start/tet:te-label/tet:technology" {
       when "../../../../../../../../../../"
          + "nw:network-types/tet:te-topology/"
          + "otnt:otn-topology" {
         description
           "Augmentation parameters apply only for networks with
            OTN topology type.";
       }
       description
         "Augment TE label range start for the source LTP
          of the connectivity matrix entry information source.";
       case otn {
         uses l1-types:otn-label-start-end;
       }
     }
     augment "/nw:networks/nw:network/nw:node/tet:te/"
           + "tet:information-source-entry/tet:connectivity-matrices/"
           + "tet:connectivity-matrix/"
           + "tet:from/tet:label-restrictions/"
           + "tet:label-restriction/"
           + "tet:label-end/tet:te-label/tet:technology" {
       when "../../../../../../../../../../"
          + "nw:network-types/tet:te-topology/"
          + "otnt:otn-topology" {
         description
           "Augmentation parameters apply only for networks with
            OTN topology type.";
       }
       description
         "Augment TE label range end for the source LTP
          of the connectivity matrix entry information source.";
       case otn {
         uses l1-types:otn-label-start-end;
       }
     }

     augment "/nw:networks/nw:network/nw:node/tet:te/"




           + "tet:information-source-entry/tet:connectivity-matrices/"
           + "tet:connectivity-matrix/"
           + "tet:from/tet:label-restrictions/"
           + "tet:label-restriction/"
           + "tet:label-step/tet:technology" {
       when "../../../../../../../../../"
          + "nw:network-types/tet:te-topology/"
          + "otnt:otn-topology" {
         description
           "Augmentation parameters apply only for networks with
            OTN topology type.";
       }
       description
         "Augment TE label range step for the source LTP
          of the connectivity matrix entry information source.";
       case otn {
         uses l1-types:otn-label-step;
       }
     }

     augment "/nw:networks/nw:network/nw:node/tet:te/"
           + "tet:information-source-entry/tet:connectivity-matrices/"
           + "tet:connectivity-matrix/"
           + "tet:to/tet:label-restrictions/tet:label-restriction/"
           + "tet:label-start/tet:te-label/tet:technology" {
       when "../../../../../../../../../../"
          + "nw:network-types/tet:te-topology/"
          + "otnt:otn-topology" {
         description
           "Augmentation parameters apply only for networks with
            OTN topology type.";
       }
       description
         "Augment TE label range start for the destination LTP
          of the connectivity matrix entry information source.";
       case otn {
         uses l1-types:otn-label-start-end;
       }
     }

     augment "/nw:networks/nw:network/nw:node/tet:te/"
           + "tet:information-source-entry/tet:connectivity-matrices/"
           + "tet:connectivity-matrix/"
           + "tet:to/tet:label-restrictions/tet:label-restriction/"
           + "tet:label-end/tet:te-label/tet:technology" {
       when "../../../../../../../../../../"
          + "nw:network-types/tet:te-topology/"
          + "otnt:otn-topology" {




         description
           "Augmentation parameters apply only for networks with
            OTN topology type.";
       }
       description
         "Augment TE label range end for the destination LTP
          of the connectivity matrix entry information source.";
       case otn {
         uses l1-types:otn-label-start-end;
       }
     }

     augment "/nw:networks/nw:network/nw:node/tet:te/"
           + "tet:information-source-entry/tet:connectivity-matrices/"
           + "tet:connectivity-matrix/"
           + "tet:to/tet:label-restrictions/tet:label-restriction/"
           + "tet:label-step/tet:technology" {
       when "../../../../../../../../../"
          + "nw:network-types/tet:te-topology/"
          + "otnt:otn-topology" {
         description
           "Augmentation parameters apply only for networks with
            OTN topology type.";
       }
       description
         "Augment TE label range step for the destination LTP
          of the connectivity matrix entry information source.";
       case otn {
         uses l1-types:otn-label-step;
       }
     }

     augment "/nw:networks/nw:network/nw:node/tet:te/"
           + "tet:information-source-entry/tet:connectivity-matrices/"
           + "tet:connectivity-matrix/"
           + "tet:underlay/tet:primary-path/tet:path-element/tet:type/"
           + "tet:label/tet:label-hop/tet:te-label/tet:technology" {
       when "../../../../../../../../../../"
          + "nw:network-types/tet:te-topology/"
          + "otnt:otn-topology" {
         description
           "Augmentation parameters apply only for networks with
            OTN topology type.";
       }
       description
         "Augment TE label hop for the underlay primary path
          of the connectivity matrix entry information source.";
       case otn {




         uses l1-types:otn-label-hop;
       }
     }

     augment "/nw:networks/nw:network/nw:node/tet:te/"
           + "tet:information-source-entry/tet:connectivity-matrices/"
           + "tet:connectivity-matrix/"
           + "tet:underlay/tet:backup-path/tet:path-element/tet:type/"
           + "tet:label/tet:label-hop/tet:te-label/tet:technology" {
       when "../../../../../../../../../../"
          + "nw:network-types/tet:te-topology/"
          + "otnt:otn-topology" {
         description
           "Augmentation parameters apply only for networks with
            OTN topology type.";
       }
       description
         "Augment TE label hop for the underlay backup path
          of the connectivity matrix entry information source.";
       case otn {
         uses l1-types:otn-label-hop;
       }
     }

     augment "/nw:networks/nw:network/nw:node/tet:te/"
           + "tet:information-source-entry/tet:connectivity-matrices/"
           + "tet:connectivity-matrix/"
           + "tet:optimizations/tet:algorithm/tet:metric/"
           + "tet:optimization-metric/"
           + "tet:explicit-route-exclude-objects/"
           + "tet:route-object-exclude-object/tet:type/"
           + "tet:label/tet:label-hop/tet:te-label/tet:technology" {
       when "../../../../../../../../../../../"
          + "nw:network-types/tet:te-topology/"
          + "otnt:otn-topology" {
         description
           "Augmentation parameters apply only for networks with
            OTN topology type.";
       }
       description
         "Augment TE label hop for the explicit route objects excluded
          by the path computation of the connectivity matrix entry
          information source.";
       case otn {
         uses l1-types:otn-label-hop;
       }
     }




     augment "/nw:networks/nw:network/nw:node/tet:te/"
           + "tet:information-source-entry/tet:connectivity-matrices/"
           + "tet:connectivity-matrix/"
           + "tet:optimizations/tet:algorithm/tet:metric/"
           + "tet:optimization-metric/"
           + "tet:explicit-route-include-objects/"
           + "tet:route-object-include-object/tet:type/"
           + "tet:label/tet:label-hop/tet:te-label/tet:technology" {
       when "../../../../../../../../../../../"
          + "nw:network-types/tet:te-topology/"
          + "otnt:otn-topology" {
         description
           "Augmentation parameters apply only for networks with
            OTN topology type.";
       }
       description
         "Augment TE label hop for the explicit route objects included
          by the path computation of the connectivity matrix entry
          information source.";
       case otn {
         uses l1-types:otn-label-hop;
       }
     }

     augment "/nw:networks/nw:network/nw:node/tet:te/"
           + "tet:information-source-entry/tet:connectivity-matrices/"
           + "tet:connectivity-matrix/"
           + "tet:path-properties/tet:path-route-objects/"
           + "tet:path-route-object/tet:type/"
           + "tet:label/tet:label-hop/tet:te-label/tet:technology" {
       when "../../../../../../../../../../"
          + "nw:network-types/tet:te-topology/"
          + "otnt:otn-topology" {
         description
           "Augmentation parameters apply only for networks with
            OTN topology type.";
       }
       description
         "Augment TE label hop for the computed path route objects
          of the connectivity matrix entry information source.";
       case otn {
         uses l1-types:otn-label-hop;
       }
     }

     augment "/nw:networks/nw:network/nw:node/tet:te/"
         + "tet:tunnel-termination-point/"
         + "tet:local-link-connectivities/"




         + "tet:label-restrictions/tet:label-restriction/"
         + "tet:label-start/"
         + "tet:te-label/tet:technology" {
       when "../../../../../../../../"
          + "nw:network-types/tet:te-topology/"
          + "otnt:otn-topology" {
         description
           "Augmentation parameters apply only for networks with
            OTN topology type.";
       }
       description
         "Augment TE label range start for the TTP
          Local Link Connectivities.";
       case otn {
         uses l1-types:otn-label-start-end;
       }
     }

     augment "/nw:networks/nw:network/nw:node/tet:te/"
           + "tet:tunnel-termination-point/"
           + "tet:local-link-connectivities/"
           + "tet:label-restrictions/tet:label-restriction/"
           + "tet:label-end/"
           + "tet:te-label/tet:technology"{
       when "../../../../../../../../"
          + "nw:network-types/tet:te-topology/"
          + "otnt:otn-topology" {
         description
           "Augmentation parameters apply only for networks with
            OTN topology type.";
       }
       description
         "Augment TE label range end for the TTP
          Local Link Connectivities.";
       case otn {
         uses l1-types:otn-label-start-end;
       }
     }

     augment "/nw:networks/nw:network/nw:node/tet:te/"
           + "tet:tunnel-termination-point/"
           + "tet:local-link-connectivities/"
           + "tet:label-restrictions/tet:label-restriction/"
           + "tet:label-step/"
           + "tet:technology"{
       when "../../../../../../../"
          + "nw:network-types/tet:te-topology/"
          + "otnt:otn-topology" {




         description
           "Augmentation parameters apply only for networks with
            OTN topology type.";
       }
       description
         "Augment TE label range step for the TTP
          Local Link Connectivities.";
       case otn {
         uses l1-types:otn-label-step;
       }
     }

     augment "/nw:networks/nw:network/nw:node/tet:te/"
           + "tet:tunnel-termination-point/"
           + "tet:local-link-connectivities/"
           + "tet:underlay/tet:primary-path/tet:path-element/tet:type/"
           + "tet:label/tet:label-hop/tet:te-label/tet:technology" {
       when "../../../../../../../../../"
          + "nw:network-types/tet:te-topology/"
          + "otnt:otn-topology" {
         description
           "Augmentation parameters apply only for networks with
            OTN topology type.";
       }
       description
         "Augment TE label hop for the underlay primary path
          of the TTP Local Link Connectivities.";
       case otn {
         uses l1-types:otn-label-hop;
       }
     }

     augment "/nw:networks/nw:network/nw:node/tet:te/"
           + "tet:tunnel-termination-point/"
           + "tet:local-link-connectivities/"
           + "tet:underlay/tet:backup-path/tet:path-element/tet:type/"
           + "tet:label/tet:label-hop/tet:te-label/tet:technology" {
       when "../../../../../../../../../"
          + "nw:network-types/tet:te-topology/"
          + "otnt:otn-topology" {
         description
           "Augmentation parameters apply only for networks with
            OTN topology type.";
       }
       description
         "Augment TE label hop for the underlay backup path
          of the TTP Local Link Connectivities.";
       case otn {




         uses l1-types:otn-label-hop;
       }
     }

     augment "/nw:networks/nw:network/nw:node/tet:te/"
           + "tet:tunnel-termination-point/"
           + "tet:local-link-connectivities/"
           + "tet:optimizations/tet:algorithm/tet:metric/"
           + "tet:optimization-metric/"
           + "tet:explicit-route-exclude-objects/"
           + "tet:route-object-exclude-object/tet:type/"
           + "tet:label/tet:label-hop/tet:te-label/tet:technology" {
       when "../../../../../../../../../../"
          + "nw:network-types/tet:te-topology/"
          + "otnt:otn-topology" {
         description
           "Augmentation parameters apply only for networks with
            OTN topology type.";
       }
       description
         "Augment TE label hop for the explicit route objects excluded
          by the path computation of the TTP Local Link
          Connectivities.";
       case otn {
         uses l1-types:otn-label-hop;
       }
     }

     augment "/nw:networks/nw:network/nw:node/tet:te/"
           + "tet:tunnel-termination-point/"
           + "tet:local-link-connectivities/"
           + "tet:optimizations/tet:algorithm/tet:metric/"
           + "tet:optimization-metric/"
           + "tet:explicit-route-include-objects/"
           + "tet:route-object-include-object/tet:type/"
           + "tet:label/tet:label-hop/tet:te-label/tet:technology" {
       when "../../../../../../../../../../"
          + "nw:network-types/tet:te-topology/"
          + "otnt:otn-topology" {
         description
           "Augmentation parameters apply only for networks with
            OTN topology type.";
       }
       description
         "Augment TE label hop for the explicit route objects included
          by the path computation of the TTP Local Link
          Connectivities.";
       case otn {




         uses l1-types:otn-label-hop;
       }
     }

     augment "/nw:networks/nw:network/nw:node/tet:te/"
           + "tet:tunnel-termination-point/"
           + "tet:local-link-connectivities/"
           + "tet:path-properties/tet:path-route-objects/"
           + "tet:path-route-object/tet:type/"
           + "tet:label/tet:label-hop/tet:te-label/tet:technology" {
       when "../../../../../../../../../"
          + "nw:network-types/tet:te-topology/"
          + "otnt:otn-topology" {
         description
           "Augmentation parameters apply only for networks with
            OTN topology type.";
       }
       description
         "Augment TE label hop for the computed path route objects
          of the TTP Local Link Connectivities.";
       case otn {
         uses l1-types:otn-label-hop;
       }
     }

     augment "/nw:networks/nw:network/nw:node/tet:te/"
           + "tet:tunnel-termination-point/"
           + "tet:local-link-connectivities/"
           + "tet:local-link-connectivity/"
           + "tet:label-restrictions/tet:label-restriction/"
           + "tet:label-start/tet:te-label/tet:technology" {
       when "../../../../../../../../../"
          + "nw:network-types/tet:te-topology/"
          + "otnt:otn-topology" {
         description
           "Augmentation parameters apply only for networks with
            OTN topology type.";
       }
       description
         "Augment TE label range start for the TTP
          Local Link Connectivity entry.";
       case otn {
         uses l1-types:otn-label-start-end;
       }
     }

     augment "/nw:networks/nw:network/nw:node/tet:te/"
           + "tet:tunnel-termination-point/"




           + "tet:local-link-connectivities/"
           + "tet:local-link-connectivity/"
           + "tet:label-restrictions/tet:label-restriction/"
           + "tet:label-end/tet:te-label/tet:technology" {
       when "../../../../../../../../../"
          + "nw:network-types/tet:te-topology/"
          + "otnt:otn-topology" {
         description
           "Augmentation parameters apply only for networks with
            OTN topology type.";
       }
       description
         "Augment TE label range end for the TTP
          Local Link Connectivity entry.";
       case otn {
         uses l1-types:otn-label-start-end;
       }
     }

     augment "/nw:networks/nw:network/nw:node/tet:te/"
           + "tet:tunnel-termination-point/"
           + "tet:local-link-connectivities/"
           + "tet:local-link-connectivity/"
           + "tet:label-restrictions/tet:label-restriction/"
           + "tet:label-step/tet:technology" {
       when "../../../../../../../../"
          + "nw:network-types/tet:te-topology/"
          + "otnt:otn-topology" {
         description
           "Augmentation parameters apply only for networks with
            OTN topology type.";
       }
       description
         "Augment TE label range step for the TTP
          Local Link Connectivity entry.";
       case otn {
         uses l1-types:otn-label-step;
       }
     }

     augment "/nw:networks/nw:network/nw:node/tet:te/"
           + "tet:tunnel-termination-point/"
           + "tet:local-link-connectivities/"
           + "tet:local-link-connectivity/"
           + "tet:underlay/tet:primary-path/tet:path-element/tet:type/"
           + "tet:label/tet:label-hop/tet:te-label/tet:technology" {
       when "../../../../../../../../../../"
          + "nw:network-types/tet:te-topology/"




          + "otnt:otn-topology" {
         description
           "Augmentation parameters apply only for networks with
            OTN topology type.";
       }
       description
         "Augment TE label hop for the underlay primary path
          of the TTP Local Link Connectivity entry.";
       case otn {
         uses l1-types:otn-label-hop;
       }
     }

     augment "/nw:networks/nw:network/nw:node/tet:te/"
           + "tet:tunnel-termination-point/"
           + "tet:local-link-connectivities/"
           + "tet:local-link-connectivity/"
           + "tet:underlay/tet:backup-path/tet:path-element/tet:type/"
           + "tet:label/tet:label-hop/tet:te-label/tet:technology" {
       when "../../../../../../../../../../"
          + "nw:network-types/tet:te-topology/"
          + "otnt:otn-topology" {
         description
           "Augmentation parameters apply only for networks with
            OTN topology type.";
       }
       description
         "Augment TE label hop for the underlay backup path
          of the TTP Local Link Connectivity entry.";
       case otn {
         uses l1-types:otn-label-hop;
       }
     }

     augment "/nw:networks/nw:network/nw:node/tet:te/"
           + "tet:tunnel-termination-point/"
           + "tet:local-link-connectivities/"
           + "tet:local-link-connectivity/"
           + "tet:optimizations/tet:algorithm/tet:metric/"
           + "tet:optimization-metric/"
           + "tet:explicit-route-exclude-objects/"
           + "tet:route-object-exclude-object/tet:type/"
           + "tet:label/tet:label-hop/tet:te-label/tet:technology" {
       when "../../../../../../../../../../../"
          + "nw:network-types/tet:te-topology/"
          + "otnt:otn-topology" {
         description
           "Augmentation parameters apply only for networks with




            OTN topology type.";
       }
       description
         "Augment TE label hop for the explicit route objects excluded
          by the path computation of the TTP Local Link
          Connectivity entry.";
       case otn {
         uses l1-types:otn-label-hop;
       }
     }

     augment "/nw:networks/nw:network/nw:node/tet:te/"
           + "tet:tunnel-termination-point/"
           + "tet:local-link-connectivities/"
           + "tet:local-link-connectivity/"
           + "tet:optimizations/tet:algorithm/tet:metric/"
           + "tet:optimization-metric/"
           + "tet:explicit-route-include-objects/"
           + "tet:route-object-include-object/tet:type/"
           + "tet:label/tet:label-hop/tet:te-label/tet:technology" {
       when "../../../../../../../../../../../"
          + "nw:network-types/tet:te-topology/"
          + "otnt:otn-topology" {
         description
           "Augmentation parameters apply only for networks with
            OTN topology type.";
       }
       description
         "Augment TE label hop for the explicit route objects included
          by the path computation of the TTP Local Link
          Connectivity entry.";
       case otn {
         uses l1-types:otn-label-hop;
       }
     }

     augment "/nw:networks/nw:network/nw:node/tet:te/"
           + "tet:tunnel-termination-point/"
           + "tet:local-link-connectivities/"
           + "tet:local-link-connectivity/"
           + "tet:path-properties/tet:path-route-objects/"
           + "tet:path-route-object/tet:type/"
           + "tet:label/tet:label-hop/tet:te-label/tet:technology" {
       when "../../../../../../../../../../"
          + "nw:network-types/tet:te-topology/"
          + "otnt:otn-topology" {
         description
           "Augmentation parameters apply only for networks with




            OTN topology type.";
       }
       description
         "Augment TE label hop for the computed path route objects
          of the TTP Local Link Connectivity entry.";
       case otn {
         uses l1-types:otn-label-hop;
       }
     }
     augment "/nw:networks/nw:network/nt:link/tet:te/"
           + "tet:te-link-attributes/"
           + "tet:underlay/tet:primary-path/tet:path-element/tet:type/"
           + "tet:label/tet:label-hop/tet:te-label/tet:technology" {
       when "../../../../../../../../"
          + "nw:network-types/tet:te-topology/"
          + "otnt:otn-topology" {
         description
           "Augmentation parameters apply only for networks with
            OTN topology type.";
       }
       description
         "Augment TE label hop for the underlay primary path
          of the TE link.";
       case otn {
         uses l1-types:otn-label-hop;
       }
     }

     augment "/nw:networks/nw:network/nt:link/tet:te/"
           + "tet:te-link-attributes/"
           + "tet:underlay/tet:backup-path/tet:path-element/tet:type/"
           + "tet:label/tet:label-hop/tet:te-label/tet:technology" {
       when "../../../../../../../../"
          + "nw:network-types/tet:te-topology/"
          + "otnt:otn-topology" {
         description
           "Augmentation parameters apply only for networks with
            OTN topology type.";
       }
       description
         "Augment TE label hop for the underlay backup path
          of the TE link.";
       case otn {
         uses l1-types:otn-label-hop;
       }
     }

     augment "/nw:networks/nw:network/nt:link/tet:te/"




           + "tet:te-link-attributes/"
           + "tet:label-restrictions/tet:label-restriction/"
           + "tet:label-start/tet:te-label/tet:technology" {
       when "../../../../../../../nw:network-types/tet:te-topology/"
          + "otnt:otn-topology" {
         description
           "Augmentation parameters apply only for networks with
            OTN topology type.";
       }
       description
         "Augment TE label range start for the TE link.";
       case otn {
         uses l1-types:otn-label-start-end;
       }
     }

     augment "/nw:networks/nw:network/nt:link/tet:te/"
           + "tet:te-link-attributes/"
           + "tet:label-restrictions/tet:label-restriction/"
           + "tet:label-end/tet:te-label/tet:technology" {
       when "../../../../../../../nw:network-types/tet:te-topology/"
          + "otnt:otn-topology" {
         description
           "Augmentation parameters apply only for networks with
            OTN topology type.";
       }
       description
         "Augment TE label range end for the TE link.";
       case otn {
         uses l1-types:otn-label-start-end;
       }
     }

     augment "/nw:networks/nw:network/nt:link/tet:te/"
           + "tet:te-link-attributes/"
           + "tet:label-restrictions/tet:label-restriction/"
           + "tet:label-step/tet:technology" {
       when "../../../../../../nw:network-types/tet:te-topology/"
          + "otnt:otn-topology" {
         description
           "Augmentation parameters apply only for networks with
            OTN topology type.";
       }
       description
         "Augment TE label range step for the TE link.";
       case otn {
         uses l1-types:otn-label-step;
       }




     }

     augment "/nw:networks/nw:network/nt:link/tet:te/"
           + "tet:information-source-entry/"
           + "tet:label-restrictions/tet:label-restriction/"
           + "tet:label-start/tet:te-label/tet:technology" {
       when "../../../../../../../nw:network-types/tet:te-topology/"
          + "otnt:otn-topology" {
         description
           "Augmentation parameters apply only for networks with
            OTN topology type.";
       }
       description
         "Augment TE label range start for the TE link
          information source.";
       case otn {
         uses l1-types:otn-label-start-end;
       }
     }

     augment "/nw:networks/nw:network/nt:link/tet:te/"
           + "tet:information-source-entry/"
           + "tet:label-restrictions/tet:label-restriction/"
           + "tet:label-end/tet:te-label/tet:technology" {
       when "../../../../../../../nw:network-types/tet:te-topology/"
          + "otnt:otn-topology" {
         description
           "Augmentation parameters apply only for networks with
            OTN topology type.";
       }
       description
         "Augment TE label range end for the TE link
          information source.";
       case otn {
         uses l1-types:otn-label-start-end;
       }
     }

     augment "/nw:networks/nw:network/nt:link/tet:te/"
           + "tet:information-source-entry/"
           + "tet:label-restrictions/tet:label-restriction/"
           + "tet:label-step/tet:technology" {
       when "../../../../../../nw:network-types/tet:te-topology/"
          + "otnt:otn-topology" {
         description
           "Augmentation parameters apply only for networks with
            OTN topology type.";
       }




       description
         "Augment TE label range step for the TE link
          information source.";
       case otn {
         uses l1-types:otn-label-step;
       }
     }

     augment "/nw:networks/tet:te/tet:templates/"
           + "tet:link-template/tet:te-link-attributes/"
           + "tet:underlay/tet:primary-path/tet:path-element/tet:type/"
           + "tet:label/tet:label-hop/tet:te-label/tet:technology" {
       description
         "Augment TE label hop for the underlay primary path
          of the TE link template.";
       case otn {
         uses l1-types:otn-label-hop;
       }
     }

     augment "/nw:networks/tet:te/tet:templates/"
           + "tet:link-template/tet:te-link-attributes/"
           + "tet:underlay/tet:backup-path/tet:path-element/tet:type/"
           + "tet:label/tet:label-hop/tet:te-label/tet:technology" {
       description
         "Augment TE label hop for the underlay backup path
          of the TE link template.";
       case otn {
         uses l1-types:otn-label-hop;
       }
     }

     augment "/nw:networks/tet:te/tet:templates/"
           + "tet:link-template/tet:te-link-attributes/"
           + "tet:label-restrictions/tet:label-restriction/"
           + "tet:label-start/tet:te-label/tet:technology" {
       description
         "Augment TE label range start for the TE link template.";
       case otn {
         uses l1-types:otn-label-start-end;
       }
     }

     augment "/nw:networks/tet:te/tet:templates/"
           + "tet:link-template/tet:te-link-attributes/"
           + "tet:label-restrictions/tet:label-restriction/"
           + "tet:label-end/tet:te-label/tet:technology" {
       description




         "Augment TE label range end for the TE link template.";
       case otn {
         uses l1-types:otn-label-start-end;
       }
     }

     augment "/nw:networks/tet:te/tet:templates/"
           + "tet:link-template/tet:te-link-attributes/"
           + "tet:label-restrictions/tet:label-restriction/"
           + "tet:label-step/tet:technology" {
       description
         "Augment TE label range step for the TE link template.";
       case otn {
         uses l1-types:otn-label-step;
       }
     }
   }
